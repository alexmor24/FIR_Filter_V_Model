# SystemRequirements

## #1 (Container)
Functional Requirements

### #2 (Functional)
FR-01 The system shall acquire audio from an analog microphone.

### #7 (Functional)
FR-02 The system shall convert the analog audio into digital samples using an ADC.

### #8 (Functional)
FR-03 The system shall perform a band-stop FIR filter on the digital samples.

### #9 (Functional)
FR-04 The system shall operate in continuous real-time mode.

### #10 (Functional)
FR-05 The system shall output the filtered digital audio stream.

## #3 (Container)
Performance Requirements

### #11 (Functional)
PR-01 The system shall support audio bandwidth up to 10 kHz.

### #12 (Functional)
PR-02 The system shall use a sampling rate of 16 kHz.

### #13 (Functional)
PR-03 The FIR filter shall implement a band-stop notch at 1 kHz ± 200 Hz.

### #14 (Functional)
PR-04 The filter attenuation at stopband shall be ≥ 40 dB.

### #15 (Functional)
PR-05 The processing latency shall be ≤ 1 sample period.

## #4 (Container)
Hardware Requirements

### #16 (Functional)
HR-01 The system shall run on a TI MSP432P401R microcontroller.

### #17 (Functional)
HR-02 The system shall use a microphone compatible with ADC input.

### #18 (Functional)
HR-03 The system shall support floating-point FIR filtering.

## #5 (Container)
Interface Requirements

### #19 (Functional)
IR-01 The system shall interface with the microphone via analog input.

### #20 (Functional)
IR-02 The system shall interface with validation tools via digital debug output.

## #6 (Container)
Development Requirements

### #21 (Informational)
DR-01 The system shall use Model-Based Design techniques.

### #22 (Informational)
DR-02 The system shall follow a V-Model development workflow.

### #25 (Informational)
DR-03 The system shall maintain traceability from requirements to test cases.

### #26 (Informational)
DR-04 The system shall maintain source control using Git/GitHub.
